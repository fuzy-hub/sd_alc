;;; AutoCAD 2027 regression cases for 3.4.0 reliability and performance.
(defun alc-test--hard-check (name pass)
  (setq checks (cons (strcat (if pass "PASS " "FAIL ") name) checks))
  (alc-test--write-lines "hardening-test.log" (reverse checks)))

(defun alc-test--hard-wall (y)
  (alc-test--create-wall (list (list 0.0 y 0.0) (list 3000.0 y 0.0)
    (list 3000.0 (+ y 200.0) 0.0) (list 0.0 (+ y 200.0) 0.0))))

(defun alc-test--hard-color (object property / value result)
  (setq value (vlax-get-property object property)
        result (list (vla-get-ColorMethod value) (vla-get-Red value)
          (vla-get-Green value) (vla-get-Blue value) (vla-get-ColorIndex value)))
  (vlax-release-object value) result)

(defun alc-test--hard-set-rgb (object property r g b / value)
  (setq value (vlax-get-property object property))
  (vla-SetRGB value r g b) (vlax-put-property object property value)
  (vlax-release-object value))

(defun alc-test--hard-origin (object)
  (vlax-safearray->list (vlax-variant-value (vla-get-Origin object))))

(defun alc-test--hard-properties (hatch)
  (list (alc-test--hard-color hatch 'TrueColor) (alc-test--hard-color hatch 'BackgroundColor)
    (vla-get-EntityTransparency hatch) (vla-get-Layer hatch)
    (alc-test--hard-origin hatch) (vla-get-PatternAngle hatch) (vla-get-PatternScale hatch)))

(defun alc-test--hard-geometry (/ wall other hatch data before result)
  (alc-test--clear)
  (setq wall (alc-test--hard-wall 0.0) hatch (car (alc--find-boundary-hatches wall))
        other (alc--create-lwpolyline-wcs
          '((4000.0 0.0 0.0) (5000.0 0.0 0.0) (5000.0 200.0 0.0) (4000.0 200.0 0.0)) T '(0.0 0.0 1.0)))
  (alc--append-hatch-loop (vlax-ename->vla-object hatch) other)
  (vla-Evaluate (vlax-ename->vla-object hatch))
  (setq before (entget hatch))
  (alc-test--hard-check "shared-hatch-rejected-and-entire-hatch-kept"
    (and (not (alc--draw-door-opening wall '(-100.0 100.0 0.0) '(1000.0 100.0 0.0)))
         (entget wall) (entget other) (equal before (entget hatch))))
  (alc-test--hard-check "shared-hatch-pick-is-ambiguous" (not (alc--resolve-wall hatch)))
  (alc-test--clear)
  (setq wall (alc-test--hard-wall 0.0) data (entget wall))
  (setq data (subst '(42 . 0.5) (assoc 42 data) data))
  (entmod data)
  (setq before (entget wall))
  (alc-test--hard-check "curved-wall-rejected-without-changes"
    (and (not (alc--draw-door-opening wall '(-100.0 100.0 0.0) '(1000.0 100.0 0.0)))
         (equal before (entget wall))))
  (alc-test--hard-check "large-coordinate-polygon-is-valid"
    (alc--valid-polygon-p '((1000000000.0 1000000000.0 0.0) (1000001000.0 1000000000.0 0.0)
      (1000001000.0 1000000200.0 0.0) (1000000000.0 1000000200.0 0.0)) '(0.0 0.0 1.0)))
  (alc-test--hard-check "bow-tie-rejected"
    (not (alc--valid-polygon-p '((0.0 0.0 0.0) (100.0 100.0 0.0) (0.0 100.0 0.0) (100.0 0.0 0.0)) '(0.0 0.0 1.0))))
  (alc-test--hard-check "collinear-overlap-rejected"
    (not (alc--valid-polygon-p '((0.0 0.0 0.0) (100.0 0.0 0.0) (100.0 100.0 0.0)
      (20.0 0.0 0.0) (80.0 0.0 0.0) (0.0 100.0 0.0)) '(0.0 0.0 1.0))))
  (alc-test--hard-check "nonplanar-polygon-rejected"
    (not (alc--valid-polygon-p '((0.0 0.0 0.0) (100.0 0.0 0.0) (100.0 100.0 1.0) (0.0 100.0 0.0)) '(0.0 0.0 1.0))))
  ;; Spiral-shaped strip: extending its inner endpoint crosses an earlier leg.
  (alc-test--clear)
  (setq wall (alc--create-lwpolyline-wcs
    '((0.0 0.0 0.0) (1000.0 0.0 0.0) (1000.0 1000.0 0.0) (300.0 1000.0 0.0)
      (300.0 300.0 0.0) (500.0 300.0 0.0) (500.0 800.0 0.0) (800.0 800.0 0.0)
      (800.0 200.0 0.0) (0.0 200.0 0.0)) T '(0.0 0.0 1.0)) before (entget wall))
  (alc-test--hard-check "xtend-crossing-keeps-original"
    (and (not (alc--extend-wall wall '(400.0 300.0 0.0) 400.0)) (equal before (entget wall)))))

(defun alc-test--hard-door (/ wall hatch original expected result selection i object data layer before boundaries saved)
  (alc-test--clear)
  (setq wall (alc-test--hard-wall 0.0) hatch (vlax-ename->vla-object (car (alc--find-boundary-hatches wall))))
  (if (not (tblobjname "LAYER" "ALC_TEST_HATCH"))
    (entmakex '((0 . "LAYER") (100 . "AcDbSymbolTableRecord") (100 . "AcDbLayerTableRecord")
      (2 . "ALC_TEST_HATCH") (70 . 0) (62 . 3) (6 . "Continuous"))))
  (vla-put-Layer hatch "ALC_TEST_HATCH")
  (alc-test--hard-set-rgb hatch 'TrueColor 12 123 234)
  (alc-test--hard-set-rgb hatch 'BackgroundColor 230 221 212)
  (vla-put-EntityTransparency hatch "60")
  (vla-put-Origin hatch (vlax-make-variant
    (vlax-safearray-fill (vlax-make-safearray vlax-vbDouble '(0 . 1)) '(123.0 456.0))))
  (alc-test--hard-set-rgb (vlax-ename->vla-object wall) 'TrueColor 77 88 99)
  (vla-put-Lineweight (vlax-ename->vla-object wall) 35)
  (regapp "ALC_TEST")
  (entmod (append (entget wall) '((-3 ("ALC_TEST" (1000 . "preserve-me"))))))
  (setq expected (alc-test--hard-properties hatch)
        original (alc-test--hard-color (vlax-ename->vla-object wall) 'TrueColor)
        *alc-door-width* 900.0
        result (alc--draw-door-opening wall '(-100.0 100.0 0.0) '(1000.0 100.0 0.0)))
  (alc-test--hard-check "door-created-with-styled-hatch" result)
  (setq selection (ssget "_X" '((0 . "HATCH"))) i 0 result (and selection (= (sslength selection) 2)))
  (if selection (repeat (sslength selection)
    (setq object (vlax-ename->vla-object (ssname selection i)) i (1+ i))
    (if (not (equal expected (alc-test--hard-properties object) 1e-7)) (setq result nil))))
  (alc-test--hard-check "both-hatches-preserve-rgb-background-opacity-origin-layer" result)
  (setq selection (ssget "_X" '((0 . "LWPOLYLINE"))) i 0 result (= (sslength selection) 2))
  (repeat (sslength selection)
    (setq object (vlax-ename->vla-object (ssname selection i)) i (1+ i))
    (if (not (and (equal original (alc-test--hard-color object 'TrueColor)) (= (vla-get-Lineweight object) 35)))
      (setq result nil)))
  (alc-test--hard-check "both-boundaries-preserve-rgb-and-lineweight" result)
  (setq i 0 result T)
  (repeat (sslength selection)
    (if (not (equal (assoc -3 (entget (ssname selection i) '("ALC_TEST")))
      '(-3 ("ALC_TEST" (1000 . "preserve-me"))))) (setq result nil))
    (setq i (1+ i)))
  (alc-test--hard-check "both-boundaries-preserve-XData" result)
  ;; Locked hatch layer must be rejected before any replacement is created.
  (alc-test--clear)
  (setq wall (alc-test--hard-wall 0.0) hatch (car (alc--find-boundary-hatches wall)))
  (vla-put-Layer (vlax-ename->vla-object hatch) "ALC_TEST_HATCH")
  (setq layer (tblobjname "LAYER" "ALC_TEST_HATCH") data (entget layer) before (entget wall))
  (entmod (subst (cons 70 (logior 4 (cdr (assoc 70 data)))) (assoc 70 data) data))
  (alc-test--hard-check "locked-hatch-layer-rejected"
    (and (not (alc--draw-door-opening wall '(-100.0 100.0 0.0) '(1000.0 100.0 0.0)))
         (equal before (entget wall)) (= (alc-test--entity-count "LWPOLYLINE") 1)))
  (entmod data)
  ;; Force failure after the original hatch is erased; restoration must be complete.
  (defun alc--erase-for-door (entity)
    (entdel entity) (setq *alc-door-erased* (cons entity *alc-door-erased*))
    nil)
  (setq saved (entget hatch))
  (alc-test--hard-check "erase-stage-failure-restores-original-and-cleans-replacements"
    (and (not (alc--draw-door-opening wall '(-100.0 100.0 0.0) '(1000.0 100.0 0.0)))
         (equal before (entget wall)) (equal saved (entget hatch))
         (= (alc-test--entity-count "LWPOLYLINE") 1) (= (alc-test--entity-count "HATCH") 1)))
  (load (strcat (alc-test--root) "/src/alc-safety.lsp"))
  ;; Hatch creation failure is atomic for direct VV/VVC wall construction helper.
  (alc-test--clear)
  (setq wall (alc--track-temp (alc--create-lwpolyline-wcs
    '((0.0 0.0 0.0) (1000.0 0.0 0.0) (1000.0 200.0 0.0) (0.0 200.0 0.0)) T '(0.0 0.0 1.0))))
  (defun alc--make-hatch (boundary) nil)
  (alc-test--hard-check "new-wall-hatch-failure-leaves-no-boundary"
    (and (not (alc--commit-wall wall)) (= (alc-test--entity-count "LWPOLYLINE") 0)))
  (load (strcat (alc-test--root) "/src/alc-wall.lsp")))

(defun alc-test--hard-align (/ a b before-a before-b target actual)
  (alc-test--clear)
  (vl-cmdf "_.UCS" "_Z" 45.0)
  (setq a (entmakex (list '(0 . "TEXT") '(100 . "AcDbEntity") '(8 . "0")
      '(100 . "AcDbText") (cons 10 (trans '(100.0 50.0 0.0) 1 0))
      '(40 . 10.0) '(1 . "ALIGN") (cons 50 (/ pi 4.0)) '(7 . "Standard")))
        b (entmakex (list '(0 . "TEXT") '(100 . "AcDbEntity") '(8 . "0")
      '(100 . "AcDbText") (cons 10 (trans '(500.0 250.0 0.0) 1 0))
      '(40 . 70.0) '(1 . "ALIGN") (cons 50 (/ pi 4.0)) '(7 . "Standard")))
        before-a (entget a) before-b (trans (cdr (assoc 10 (entget b))) 0 1)
        target (alc--text-left-x-ucs a))
  (alc-test--hard-check "UCS45-reference-measurement-is-read-only"
    (and (numberp target) (equal before-a (entget a)) (= (alc-test--entity-count "TEXT") 2)))
  (alc-test--hard-check "UCS45-bounds-match-horizontal-text-origin"
    (and (numberp target) (>= target 99.0) (<= target 102.0)))
  (alc-test--hard-check "UCS45-align-different-text-heights"
    (and (alc--move-text-left-to-ucs-x b target)
         (equal target (alc--text-left-x-ucs b) 1e-6)
         (equal (cadr before-b) (cadr (trans (cdr (assoc 10 (entget b))) 0 1)) 1e-6)
         (= (alc-test--entity-count "TEXT") 2)))
  (vl-cmdf "_.UCS" "_World"))

(defun alc-test--hard-index (/ wall seed hatch expected start baseline indexed count i copy)
  (alc-test--clear)
  (setq wall (alc-test--hard-wall 0.0) seed (alc-test--hard-wall 1000.0)
        hatch (vlax-ename->vla-object (car (alc--find-boundary-hatches seed))))
  (repeat 1000 (setq copy (vla-Copy hatch)) (vlax-release-object copy))
  (setq *alc-hatch-scan-count* 0 start (getvar "MILLISECS"))
  (repeat 20 (setq expected (alc--find-boundary-hatches wall)))
  (setq baseline (- (getvar "MILLISECS") start) count *alc-hatch-scan-count*
        *alc-hatch-scan-count* 0 start (getvar "MILLISECS"))
  (alc--build-hatch-index)
  (setq i 0)
  (repeat 20 (if (equal expected (alc--find-boundary-hatches wall)) (setq i (1+ i))))
  (setq indexed (- (getvar "MILLISECS") start))
  (alc-test--hard-check "index-equals-scan-for-all-lookups" (= i 20))
  (alc-test--hard-check "index-reduces-twenty-database-scans-to-one"
    (and (= count 20) (= *alc-hatch-scan-count* 1)))
  (setq checks (cons (strcat "INFO benchmark hatch=1002 lookups=20 scan_ms=" (itoa baseline)
    " index_build_plus_lookup_ms=" (itoa indexed)) checks))
  (alc-test--write-lines "hardening-test.log" (reverse checks))
  (alc--end-hatch-index)
  (alc-test--hard-check "index-released-after-command" (not *alc-hatch-index*)))

(defun alc-test--hard-loader (/ pinned path result before)
  (alc-test--clear)
  (setq pinned *alc-install-root* path (strcat (getenv "ALCWALL_TEST_RUN") "/broken")
        before (alc-test--entity-count "LWPOLYLINE"))
  (vl-mkdir path)
  (setq *alc-install-root* path *alc-test-stale-command-ran* nil)
  (defun c:VV () (setq *alc-test-stale-command-ran* T))
  (defun c:VVSUMTABLE () (setq *alc-test-stale-command-ran* T))
  (load (strcat pinned "/ALCWALL.lsp"))
  (alc-test--hard-check "incomplete-installation-fails-closed" (not *alc-ready*))
  (c:VV)
  (c:VVSUMTABLE)
  (alc-test--hard-check "stale-command-is-blocked-after-load-failure"
    (and (not *alc-test-stale-command-ran*) (= before (alc-test--entity-count "LWPOLYLINE"))))
  (setq *alc-install-root* pinned)
  (load (strcat pinned "/ALCWALL.lsp"))
  (alc-test--hard-check "complete-installation-recovers" (alc--ready-p)))

(defun alc-test-run-hardening (/ checks)
  (setq checks nil)
  (alc-test--hard-geometry)
  (alc-test--hard-door)
  (alc-test--hard-align)
  (alc-test--hard-index)
  (alc-test--hard-loader)
  (princ))
(princ)

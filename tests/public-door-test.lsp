;;; Exercise the same public commands a user types, then inspect their table.
(defun alc-test-public-door-prepare ()
  (alc-test--clear)
  (setq *alc-pattern* "ANSI37" *alc-thickness* 100.0 *alc-stat-text-height* 100.0)
  (setvar "CLAYER" "ALC_wall default")
  (setvar "OSMODE" 0)
  (setvar "DYNMODE" 0)
  (setvar "ORTHOMODE" 0)
  (alc--save-settings)
  (command-s "_.ZOOM" "_Window" '(-1000.0 -1000.0 0.0) '(16000.0 6000.0 0.0))
  (princ))

(defun alc-test-public-door-check (/ selection table checks)
  (setq checks nil selection (ssget "_X" '((0 . "ACAD_TABLE"))))
  (if (and selection (= (sslength selection) 1))
    (setq table (vlax-ename->vla-object (ssname selection 0))))
  (setq checks (list
    (strcat (if (and (= (alc-test--entity-count "LWPOLYLINE") 4)
                    (= (alc-test--entity-count "HATCH") 4)) "PASS " "FAIL ")
      "VV-VVC-ALCDOOR-VVDOOR-created-four-survivors")
    (strcat (if (and table (= (vla-get-Rows table) 9)
                    (= (vla-GetText table 0 0) "PUBLIC WALL DOORS")) "PASS " "FAIL ")
      "ALCTKT-public-table-title-and-row-count")
    (strcat (if (and table (equal (distof (vla-GetText table 3 3) 2) 11.0 1e-6)) "PASS " "FAIL ")
      "ALCTKT-public-gross-wall-length-11m")
    (strcat (if (and table (= (vla-GetText table 6 1) "900") (= (vla-GetText table 6 2) "1")
                    (= (vla-GetText table 7 1) "1200") (= (vla-GetText table 7 2) "1")
                    (= (vla-GetText table 8 2) "2")) "PASS " "FAIL ")
      "ALCTKT-public-door-900-and-1200-one-each")
    (strcat (if (and table
      (equal (vla-GetCellTextHeight table 4 0) 100.0 1e-6)
      (equal (vla-GetCellTextHeight table 5 1) 100.0 1e-6)
      (equal (vla-GetCellTextHeight table 6 2) 100.0 1e-6)
      (equal (vla-GetCellTextHeight table 7 2) 100.0 1e-6)
      (equal (vla-GetCellTextHeight table 8 2) 100.0 1e-6)) "PASS " "FAIL ")
      "ALCTKT-door-section-cell-text-heights-match-wall-text")))
  (alc-test--write-lines "public-door-test.log" checks)
  (princ))

(defun alc-test-public-door-save (/ selection table)
  (setq selection (ssget "_X" '((0 . "ACAD_TABLE"))) table (ssname selection 0))
  (vla-SaveAs (alc--get-active-document)
    (strcat (getenv "ALCWALL_TEST_RUN") "/fixtures/public-wall-door-table.dwg"))
  (command-s "_.ZOOM" "_Object" table "")
  (command-s "_.ZOOM" "0.85x")
  (sssetfirst nil nil)
  (command-s "_.REGEN")
  (command-s "_.PNGOUT" (strcat (getenv "ALCWALL_TEST_RUN") "/public-wall-door-table.png") "_All" "")
  (princ))

(defun alc-test-run-public-door () (princ))
(princ)

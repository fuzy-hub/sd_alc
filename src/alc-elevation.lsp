(setq *alc-module-version* "3.5.0")
;;; One-bay ALC elevation prototype. All geometry is millimetres in current UCS.
;;; Bounds are layout-study inputs, not structural/fire-system approval.
(defun alc--mc-v (key cfg) (cdr (assoc key cfg)))
(defun alc--mc-defaults ()
  '((length . 6000.0) (floor . 0.0) (slab . 150.0) (tie-base . 1500.0)
    (top . 3300.0) (ceiling . 3000.0) (beam . 300.0) (top-slab . 150.0)
    (tie-max . 200.0) (foam-max . 150.0)))

(defun alc--mc-ranges (maximum / values value)
  (setq value 100.0)
  (while (<= value (+ maximum 1e-7))
    (setq values (cons value values) value (+ value 5.0)))
  (if (and values (not (equal (car values) maximum 1e-7))) (setq values (cons maximum values)))
  (reverse values))

(defun alc--mc-heights (height / n last-height values split)
  (if (>= height (- 100.0 1e-7))
    (progn
      (setq n (fix (/ (+ height 5.0) 605.0)))
      (if (< (* n 605.0) (- (+ height 5.0) 1e-7)) (setq n (1+ n)))
      (setq n (max 1 n) last-height (- height (* (1- n) 605.0)))
      (repeat (1- n) (setq values (cons 600.0 values)))
      (if (< last-height (- 100.0 1e-7))
        (if (> n 1)
          (progn
            (setq values (cdr values) split (* 5.0 (fix (/ (+ 600.0 last-height) 10.0))))
            (setq values (append (reverse values) (list split (- (+ 600.0 last-height) split)))))
          (setq values nil))
        (setq values (append (reverse values) (list last-height))))
      values)))

(defun alc--mc-widths (span first / rest values count last-width delta)
  (if (>= span (- 200.0 1e-7))
    (if (<= span 1100.0) (list span)
      (progn
        (setq first (min first span) rest (- span first) count 0)
        (while (> rest (+ 1105.0 1e-7)) (setq rest (- rest 1105.0) count (1+ count)))
        (setq last-width (- rest 5.0))
        (if (< last-width (- 200.0 1e-7))
          (setq delta (- 200.0 last-width) first (- first delta) last-width 200.0))
        (if (>= first (- 200.0 1e-7))
          (progn
            (setq values (list first))
            (repeat count (setq values (append values (list 1100.0))))
            (append values (list last-width))))))))

;;; Pieces: (x y width height). Alternate full/half nominal starts; shift the
;;; starting cut when needed to keep both end pieces at least 200 mm long.
(defun alc--mc-zone (span bottom heights phase / row y x widths width height pieces valid)
  (setq row 0 y bottom valid (and heights T))
  (foreach height heights
    (setq widths (alc--mc-widths span (if (= (rem (+ row phase) 2) 0) 1100.0 550.0)) x 0.0)
    (if (not widths) (setq valid nil))
    (foreach width widths
      (setq pieces (cons (list x y width height) pieces) x (+ x width 5.0)))
    (setq y (+ y height 5.0) row (1+ row)))
  (if valid (reverse pieces)))

;;; First-fit guillotine reuse, no rotation and zero saw kerf in this preview.
;;; Free rectangles from one stock brick never overlap. Small remainders are
;;; counted as scrap; reusable remainders remain available to later pieces.
(defun alc--mc-cutting (pieces / sorted piece w h free fit candidate area stock reused cuts scrap
    remnant rw rh split-a split-b candidates keep-a keep-b used)
  (setq sorted (mapcar '(lambda (i) (nth i pieces))
    (vl-sort-i pieces '(lambda (a b) (> (* (nth 2 a) (nth 3 a)) (* (nth 2 b) (nth 3 b)))))))
  (setq stock 0 reused 0 cuts 0 scrap 0.0 used 0.0)
  (foreach piece sorted
    (setq w (nth 2 piece) h (nth 3 piece) fit nil area nil used (+ used (* w h)))
    (if (or (< w 1099.999999) (< h 599.999999)) (setq cuts (1+ cuts)))
    (foreach candidate free
      (if (and (>= (+ (car candidate) 1e-7) w) (>= (+ (cadr candidate) 1e-7) h)
               (or (not area) (< (* (car candidate) (cadr candidate)) area)))
        (setq fit candidate area (* (car candidate) (cadr candidate)))))
    (if fit
      (setq free (vl-remove-if '(lambda (p) (eq p fit)) free) reused (1+ reused))
      (setq fit '(1100.0 600.0) stock (1+ stock)))
    (setq rw (- (car fit) w) rh (- (cadr fit) h)
          split-a (list (list rw (cadr fit)) (list w rh))
          split-b (list (list rw h) (list (car fit) rh)) keep-a 0.0 keep-b 0.0)
    (foreach remnant split-a
      (if (and (>= (car remnant) 199.999999) (>= (cadr remnant) 99.999999))
        (setq keep-a (+ keep-a (* (car remnant) (cadr remnant))))))
    (foreach remnant split-b
      (if (and (>= (car remnant) 199.999999) (>= (cadr remnant) 99.999999))
        (setq keep-b (+ keep-b (* (car remnant) (cadr remnant))))))
    (foreach remnant (if (>= keep-a keep-b) split-a split-b)
      (if (and (> (car remnant) 1e-7) (> (cadr remnant) 1e-7))
        (if (and (>= (car remnant) 199.999999) (>= (cadr remnant) 99.999999))
          (setq free (cons remnant free))
          (setq scrap (+ scrap (* (car remnant) (cadr remnant))))))))
  (list (cons 'stock stock) (cons 'reused reused) (cons 'cut-pieces cuts)
    (cons 'scrap scrap) (cons 'used-area used)
    (cons 'reusable-area (apply '+ (cons 0.0 (mapcar '(lambda (p) (* (car p) (cadr p))) free))))))

(defun alc--mc-better (left right / a b decided better)
  (if (not right) T
    (progn
      (setq a left b right)
      (while (and a (not decided))
        (if (not (equal (car a) (car b) 1e-6))
          (setq better (< (car a) (car b)) decided T))
        (setq a (cdr a) b (cdr b)))
      better)))

(defun alc--mc-valid-config (cfg)
  (and (>= (alc--mc-v 'length cfg) 200.0)
       (> (alc--mc-v 'slab cfg) 0.0) (> (alc--mc-v 'top-slab cfg) 0.0)
       (>= (alc--mc-v 'beam cfg) 0.0)
       (>= (alc--mc-v 'tie-max cfg) 100.0) (>= (alc--mc-v 'foam-max cfg) 100.0)
       (>= (- (alc--mc-v 'tie-base cfg) (alc--mc-v 'floor cfg)) 120.0)
       (>= (- (alc--mc-v 'top cfg) (alc--mc-v 'tie-base cfg)) 310.0)))

(defun alc--mc-plan (cfg / lower tie foam upper heights phase pieces stats score best best-score span)
  (if (alc--mc-valid-config cfg)
    (progn
      (setq span (alc--mc-v 'length cfg)
            lower (alc--mc-heights (- (alc--mc-v 'tie-base cfg) (alc--mc-v 'floor cfg) 20.0)))
      (foreach tie (alc--mc-ranges (alc--mc-v 'tie-max cfg))
        (foreach foam (alc--mc-ranges (alc--mc-v 'foam-max cfg))
          (setq upper (alc--mc-heights (- (alc--mc-v 'top cfg) (alc--mc-v 'tie-base cfg) tie 10.0 foam)) phase 0)
          (if (and lower upper)
            (repeat 2
              (setq pieces (append
                (alc--mc-zone span (+ (alc--mc-v 'floor cfg) 10.0) lower phase)
                (alc--mc-zone span (+ (alc--mc-v 'tie-base cfg) tie 10.0) upper phase)))
              (if pieces
                (progn
                  (setq stats (alc--mc-cutting pieces)
                        score (list (alc--mc-v 'scrap stats) (alc--mc-v 'stock stats)
                          (alc--mc-v 'cut-pieces stats) (+ (abs (- tie 150.0)) (abs (- foam 100.0)))))
                  (if (alc--mc-better score best-score)
                    (setq best-score score best (append (list (cons 'tie tie) (cons 'foam foam)
                      (cons 'phase phase) (cons 'lower lower) (cons 'upper upper) (cons 'pieces pieces)) stats)))))
              (setq phase (1+ phase))))))
      best)))

(defun alc--mc-point (origin x y)
  (trans (list (+ (car origin) x) (+ (cadr origin) y) (caddr origin)) 1 0))
(defun alc--mc-rect (origin x y width height layer / entity)
  (setq entity (alc--create-lwpolyline-wcs-on-layer
    (list (alc--mc-point origin x y) (alc--mc-point origin (+ x width) y)
      (alc--mc-point origin (+ x width) (+ y height)) (alc--mc-point origin x (+ y height)))
    T (trans '(0.0 0.0 1.0) 1 0 T) layer))
  (if entity (alc--track-temp entity) (vl-exit-with-error "Khong ve duoc hinh chu nhat.")))
(defun alc--mc-line (origin x1 y1 x2 y2 layer / object)
  (setq object (vla-AddLine (alc--current-space) (vlax-3d-point (alc--mc-point origin x1 y1))
    (vlax-3d-point (alc--mc-point origin x2 y2))))
  (alc--track-temp (vlax-vla-object->ename object)) (vla-put-Layer object layer) object)
(defun alc--mc-text (origin x y text height layer / object normal)
  (setq object (vla-AddText (alc--current-space) text (vlax-3d-point (alc--mc-point origin x y)) height))
  (alc--track-temp (vlax-vla-object->ename object))
  (vla-put-Normal object (vlax-3d-point (trans '(0.0 0.0 1.0) 1 0 T)))
  (vla-put-Rotation object (angle '(0.0 0.0 0.0) (trans (trans '(1.0 0.0 0.0) 1 0 T) 0 (trans '(0.0 0.0 1.0) 1 0 T) T)))
  (vla-put-InsertionPoint object (vlax-3d-point (alc--mc-point origin x y)))
  (vla-put-Layer object layer) object)
(defun alc--mc-hatched (origin y width height layer pattern scale / boundary hatch)
  (setq boundary (alc--mc-rect origin 0.0 y width height layer)
        hatch (alc--make-hatch-with-settings boundary pattern 256 scale 0))
  (if (not hatch) (vl-exit-with-error "Khong tao duoc hatch mat cat."))
  (alc--track-temp (vlax-vla-object->ename hatch)) (vla-put-Layer hatch layer) boundary)
(defun alc--mc-dim (origin a b position / object normal)
  (setq object (vla-AddDimAligned (alc--current-space)
    (vlax-3d-point (alc--mc-point origin (car a) (cadr a)))
    (vlax-3d-point (alc--mc-point origin (car b) (cadr b)))
    (vlax-3d-point (alc--mc-point origin (car position) (cadr position)))))
  (alc--track-temp (vlax-vla-object->ename object))
  (vla-put-Normal object (vlax-3d-point (trans '(0.0 0.0 1.0) 1 0 T)))
  (vla-put-ExtLine1Point object (vlax-3d-point (alc--mc-point origin (car a) (cadr a))))
  (vla-put-ExtLine2Point object (vlax-3d-point (alc--mc-point origin (car b) (cadr b))))
  (vla-put-TextPosition object (vlax-3d-point (alc--mc-point origin (car position) (cadr position))))
  (vla-put-Layer object "ALC_MC_DIM") (vla-put-LinearScaleFactor object 1.0) object)

(defun alc--mc-layers (/ item object)
  (foreach item '(("ALC_MC_TRUC" . 1) ("ALC_MC_BETONG" . 8) ("ALC_MC_GACH" . 3)
                 ("ALC_MC_FOAM" . 6) ("ALC_MC_TRAN" . 4) ("ALC_MC_CHU" . 7) ("ALC_MC_DIM" . 2))
    (if (not (tblsearch "LAYER" (car item)))
      (progn (setq object (vla-Add (vla-get-Layers (alc--get-active-document)) (car item)))
        (vla-put-Color object (cdr item))))
    (setq object (vla-Item (vla-get-Layers (alc--get-active-document)) (car item)))
    (if (or (= (vla-get-Lock object) :vlax-true) (= (vla-get-Freeze object) :vlax-true)
            (= (vla-get-LayerOn object) :vlax-false))
      (vl-exit-with-error (strcat "Hay bat, thaw, mo khoa layer " (car item))))))

(defun alc--mc-render (cfg plan origin / span floor tie-base top beam slab top-slab tie foam piece x object upper-y datum ceiling)
  (alc--mc-layers)
  (setq span (alc--mc-v 'length cfg) floor (alc--mc-v 'floor cfg)
        tie-base (alc--mc-v 'tie-base cfg) top (alc--mc-v 'top cfg) beam (alc--mc-v 'beam cfg)
        slab (alc--mc-v 'slab cfg) top-slab (alc--mc-v 'top-slab cfg)
        tie (alc--mc-v 'tie plan) foam (alc--mc-v 'foam plan)
        upper-y (+ top beam top-slab))
  ;; Insertion is floor datum; model elevation values remain separate from drawing Y.
  (setq tie-base (- tie-base floor) top (- top floor) upper-y (- upper-y floor))
  (alc--mc-hatched origin (- slab) span slab "ALC_MC_BETONG" "AR-CONC" 3.0)
  (alc--mc-hatched origin tie-base span tie "ALC_MC_BETONG" "AR-CONC" 3.0)
  (if (> beam 1e-7) (alc--mc-hatched origin top span beam "ALC_MC_BETONG" "AR-CONC" 3.0))
  (alc--mc-hatched origin (+ top beam) span top-slab "ALC_MC_BETONG" "AR-CONC" 3.0)
  (alc--mc-hatched origin (- top foam) span foam "ALC_MC_FOAM" "ANSI31" 10.0)
  (foreach piece (alc--mc-v 'pieces plan)
    (alc--mc-rect origin (car piece) (- (cadr piece) floor) (nth 2 piece) (nth 3 piece) "ALC_MC_GACH"))
  (foreach x (list 0.0 span)
    (alc--mc-line origin x (- (- slab) 300.0) x (+ upper-y 400.0) "ALC_MC_TRUC")
    (setq object (vla-AddCircle (alc--current-space) (vlax-3d-point (alc--mc-point origin x (+ upper-y 250.0))) 100.0))
    (alc--track-temp (vlax-vla-object->ename object))
    (vla-put-Normal object (vlax-3d-point (trans '(0.0 0.0 1.0) 1 0 T)))
    (vla-put-Center object (vlax-3d-point (alc--mc-point origin x (+ upper-y 250.0))))
    (vla-put-Layer object "ALC_MC_TRUC")
    (alc--mc-text origin (- x 30.0) (+ upper-y 210.0) (if (= x 0.0) "1" "2") 80.0 "ALC_MC_TRUC"))
  (setq ceiling (alc--mc-v 'ceiling cfg))
  (if (and ceiling (> ceiling floor) (< ceiling (+ top floor)))
    (progn
      (setq object (alc--mc-line origin 0.0 (- ceiling floor) span (- ceiling floor) "ALC_MC_TRAN"))
      (if (not (tblsearch "LTYPE" "HIDDEN"))
        (vl-catch-all-apply 'vla-Load (list (vla-get-Linetypes (alc--get-active-document)) "HIDDEN" "acadiso.lin")))
      (if (tblsearch "LTYPE" "HIDDEN") (vla-put-Linetype object "HIDDEN"))
      (vla-put-Lineweight object 5)
      (alc--mc-text origin (+ span 700.0) (+ (- ceiling floor) 20.0)
        (strcat "TRAN THAM CHIEU " (rtos (/ ceiling 1000.0) 2 3)) 60.0 "ALC_MC_CHU")))
  (alc--mc-dim origin '(0.0 0.0) (list span 0.0) (list (/ span 2.0) (- (- slab) 250.0)))
  (alc--mc-dim origin (list span 0.0) (list span top) (list (+ span 350.0) (/ top 2.0)))
  (foreach datum (list (list 0.0 "MAT SAN" floor) (list tie-base "DAY GIANG" (+ floor tie-base))
      (list (+ tie-base tie) "DINH GIANG" (+ floor tie-base tie))
      (list top "DAY DAM/SAN" (+ floor top)) (list upper-y "MAT SAN TREN" (+ floor upper-y)))
    (alc--mc-text origin (+ span 700.0) (+ (car datum) 20.0)
      (strcat (cadr datum) " " (rtos (/ (caddr datum) 1000.0) 2 3)) 65.0 "ALC_MC_CHU"))
  (alc--mc-text origin (+ span 700.0) (- top (/ foam 2.0) 30.0)
    (strcat "FOAM " (rtos foam 2 0)) 50.0 "ALC_MC_CHU")
  (alc--mc-text origin 0.0 (- (- slab) 650.0)
    (strcat "VVMC 3.5.0 | GIANG " (rtos tie 2 0) " | FOAM " (rtos foam 2 0)
      " | VIEN CAP " (itoa (alc--mc-v 'stock plan)) " | MIENG CAT " (itoa (alc--mc-v 'cut-pieces plan)))
    90.0 "ALC_MC_CHU")
  (alc--mc-text origin 0.0 (- (- slab) 820.0)
    (strcat "GACH 1100x600 | MACH 5 | KHE 10 | PHE LIEU UOC TINH "
      (rtos (/ (alc--mc-v 'scrap plan) 1000000.0) 2 3) " m2 | PHAM VI THU BO TRI, CHUA DUYET CAU TAO")
    60.0 "ALC_MC_CHU")
  T)

(defun alc--mc-create (cfg plan origin / result before entity group objects)
  (setq before *alc-temp-entities* *alc-mc-last-error* nil)
  (setq result (vl-catch-all-apply 'alc--mc-render (list cfg plan origin)))
  (if (vl-catch-all-error-p result)
    (progn
      (foreach entity *alc-temp-entities*
        (if (not (member entity before))
          (progn (if (entget entity) (entdel entity)) (alc--untrack-temp entity))))
      (setq *alc-mc-last-error* (vl-catch-all-error-message result))
      (prompt (strcat "\nHuy mat cat; khong giu hinh do dang: " *alc-mc-last-error*)) nil)
    (progn
      (foreach entity *alc-temp-entities*
        (if (not (member entity before)) (setq objects (cons (vlax-ename->vla-object entity) objects))))
      (if objects
        (progn
          (setq group (vla-Add (vla-get-Groups (alc--get-active-document))
            (strcat "ALC_MC_" (vla-get-Handle (car objects)))))
          (vlax-invoke group 'AppendItems objects)))
      (foreach entity *alc-temp-entities*
        (if (not (member entity before)) (alc--untrack-temp entity)))
      T)))

(defun alc--mc-read (prompt default positive / value)
  (if positive (initget 6))
  (setq value (getreal (strcat "\n" prompt " <" (rtos default 2 0) ">: ")))
  (if value value default))
(defun alc--mc-loop (/ cfg item value plan insertion)
  (setq cfg (alc--mc-defaults))
  (prompt "\nVVMC 3.5.0 - 1 khoang khong cua. Don vi mm. Gioi han giang/foam la tham so thu bo tri.")
  (foreach item '((length "Chieu dai khoang (giua 2 truc bien tu chon)" T)
      (floor "Cao do mat san duoi" nil) (slab "Chieu day san duoi" T)
      (tie-base "Cao do DAY giang" nil) (top "Cao do ket thuc tuong = DAY dam/san" nil)
      (ceiling "Cao do tran THAM CHIEU (khong cat tuong tai day)" nil)
      (beam "Chieu cao phan dam DUOI san tren (0 = khong co dam)" nil)
      (top-slab "Chieu day san tren" T) (tie-max "Chieu cao giang toi da (min 100)" T)
      (foam-max "Chieu cao foam toi da (min 100)" T))
    (setq value (alc--mc-read (cadr item) (alc--mc-v (car item) cfg) (caddr item))
          cfg (subst (cons (car item) value) (assoc (car item) cfg) cfg)))
  (prompt "\nDang thu bo tri gach va tan dung mieng cat...")
  (if (setq plan (alc--mc-plan cfg))
    (progn
      (prompt (strcat "\nDe xuat: giang " (rtos (alc--mc-v 'tie plan) 2 0)
        ", foam " (rtos (alc--mc-v 'foam plan) 2 0) ", vien cap uoc tinh " (itoa (alc--mc-v 'stock plan)) "."))
      (if (setq insertion (getpoint "\nDiem dat mat san duoi tai truc trai <Esc huy>: "))
        (if (alc--mc-create cfg plan insertion) (prompt "\nDa tao mat cat; 1 Undo xoa ca khoang."))))
    (prompt "\nKhong co phuong an trong gioi han. Kiem tra cao do, chieu dai >=200, giang/foam max >=100. Khong tao hinh."))
  (princ))
(princ)
